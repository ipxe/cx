SeedDescriptor ::= SEQUENCE {
    generatorType               GeneratorType,
    preseedValue                OCTET STRING,
    preseedVerificationKey      SubjectPublicKeyInfo }

SeedDescriptors ::= SEQUENCE SIZE (1..MAX) OF SeedDescriptor
