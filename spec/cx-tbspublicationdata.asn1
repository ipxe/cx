TBSPublicationData ::= SEQUENCE {
    version                     PublicationVersion,
    zone                        UTF8String,
    aggregated                  BOOLEAN DEFAULT TRUE,
    publishedAt                 GeneralizedTime,
    nextUpdateNotBefore         GeneralizedTime,
    nextUpdateNotAfter          GeneralizedTime,
    excludesPublishedBefore     GeneralizedTime OPTIONAL,
    notifications               Notifications,
    updateURLs                  UpdateURLs,
    extensions              [0] Extensions OPTIONAL }
