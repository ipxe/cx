SeedReportContent ::= SEQUENCE {
    version                     SeedReportVersion,
    seedDescriptors             SeedDescriptors,
    publisherName               UTF8String,
    seedReportChallenge         UTF8String,
    extensions              [0] Extensions OPTIONAL }
