CXContactTracingV1 { iso(1) identified-organization(3) dod(6) internet(1)
                     private(4) enterprise(1) 10019 cx(3) id-mod(0)
                     id-mod-cx-v1(1) }

DEFINITIONS EXPLICIT TAGS ::= BEGIN

IMPORTS
    AlgorithmIdentifier, SubjectPublicKeyInfo
    FROM PKIX1Explicit88 { iso(1) identified-organization(3) dod(6) internet(1)
                           security(5) mechanisms(5) pkix(7) id-mod(0)
                           id-pkix1-explicit(18) }
    ContentInfo
    FROM CryptographicMessageSyntax2004 { iso(1) member-body(2) us(840)
                                          rsadsi(113549) pkcs(1) pkcs-9(9)
                                          smime(16) modules(0) cms-2004(24) };

GeneratorType ::= INTEGER { aes128-ctr-drbg-df-n2k(1),
                            aes256-ctr-drbg-df-n2k(2) }

Signature ::= SEQUENCE {
    signatureAlgorithm          AlgorithmIdentifier,
    signatureValue              OCTET STRING }

Signatures ::= SEQUENCE SIZE (1..MAX) OF Signature

Extension ::= SEQUENCE {
    extnID                      OBJECT IDENTIFIER,
    parameters                  ANY DEFINED BY extnID OPTIONAL }

Extensions ::= SEQUENCE SIZE (1..MAX) OF Extension

SeedReportVersion ::= INTEGER { v1(1) }

SeedDescriptor ::= SEQUENCE {
    generatorType               GeneratorType,
    preseedValue                OCTET STRING,
    preseedVerificationKey      SubjectPublicKeyInfo }

SeedDescriptors ::= SEQUENCE SIZE (1..MAX) OF SeedDescriptor

SeedReportContent ::= SEQUENCE {
    version                     SeedReportVersion,
    seedDescriptors             SeedDescriptors,
    publisherName               UTF8String,
    seedReportChallenge         UTF8String,
    extensions              [0] Extensions OPTIONAL }

TBSSeedReportContent ::= SEQUENCE {
    content                     SeedReportContent,
    signatureAlgorithm          AlgorithmIdentifier }

SeedReport ::= SEQUENCE {
    content                     SeedReportContent,
    signatures                  Signatures }

PublicationVersion ::= INTEGER { v1(1) }

AlertLevel ::= INTEGER { no-alert(0), debug-alert(1), expired(2),
                         unknown-alert(3), symptomatic(4), diagnosed(5) }

SeedValues ::= OCTET STRING

Notification ::= SEQUENCE {
    alertLevel                  AlertLevel,
    generatorType               GeneratorType,
    seedValues                  SeedValues }

Notifications ::= SEQUENCE SIZE (0..MAX) OF Notification

UpdateURL ::= UTF8String

UpdateURLs ::= SEQUENCE SIZE (0..MAX) OF UpdateURL

TBSPublicationData ::= SEQUENCE {
    version                     PublicationVersion,
    zone                        UTF8String,
    aggregated                  BOOLEAN DEFAULT TRUE,
    publishedAt                 GeneralizedTime,
    nextUpdateNotBefore         GeneralizedTime,
    nextUpdateNotAfter          GeneralizedTime,
    excludesPublishedBefore     GeneralizedTime OPTIONAL,
    notifications               Notifications,
    updateURLs                  UpdateURLs,
    extensions              [0] Extensions OPTIONAL }

id-ct-cx-publicationData OBJECT IDENTIFIER ::= {
    iso(1) identified-organization(3) dod(6) internet(1) private(4)
    enterprise(1) 10019 cx(3) publication(1) }

PublicationContentInfo ::= ContentInfo

END
